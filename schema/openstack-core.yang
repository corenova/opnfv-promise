module openstack-core {
  yang-version 1.1;
  namespace "urn:opnfv:promise:openstack:core";
  prefix ostack;

  import openstack-keystone { prefix keys; }
  import openstack-nova { prefix nova; }
  
  import nfv-infrastructure { prefix nfvi; }
  import access-control-models { prefix acm; }
  import ietf-yang-types { prefix yang; }
  import ietf-inet-types { prefix inet; }

  description
    "OpenStack controller module";

  revision 2016-01-19 {
    description "Basic coverage of limited intents needed for Promise";
  }
  
  identity openstack { base nfvi:manager; }

  feature os-system-admin {
    description "OpenStack system administration capability";
  }
  
  grouping os-credentials {
    uses acm:access-credentials {
      refine strategy {
        default keystone;
      }
      refine endpoint {
        default "http://localhost:5000/v2.0";
      }
    }
    container tenant {
      leaf id { type string; }
      leaf name { type string; }
    }
  }
  
  // OpenStack infrastructure stack
  augment "/nfvi:stack" {
    leaf release { type identityref { base nfvi:release; } }
    leaf distro  { type identityref { base nfvi:distro; } }

    leaf token {
      type string;
      mandatory true;
    }
    
    container services {
      config false;
      container compute {
        leaf endpoint { type inet:uri; }
        leaf-list flavors {
          type leafref {
            path "/nfvi:stack/nfvi:compute/nfvi:flavor/nfvi:id";
          }
        }
      }
    }
    //list endpoints { ct:instance-type ServiceEndpoint; }
  }

  // OpenStack system administrator configuration tree
  container admin {
    if-feature os-system-admin;
    container auth {
      uses os-credentials;
      leaf token { type yang:uuid; }
    }
  }

  rpc authenticate {
    if-feature os-system-admin;
    input {
      uses os-credentials;
    }
    output {
      leaf token { type yang:uuid; }
    }
  }

  rpc create-tenant {
    if-feature os-system-admin;
  }

  // PROVIDER INTENTS (should go into VIM module in the future)
  rpc add-provider {
    description "Register a new resource provider into reservation system";
    input {
      leaf provider-type {
        description "Select a specific resource provider type";
        type enumeration {
          enum openstack;
          enum hp;
          enum rackspace;
          enum amazon {
            status planned;
          }
          enum joyent {
            status planned;
          }
          enum azure {
            status planned;
          }
        }
        default openstack;
      }
      uses acm:access-credentials {
        refine strategy {
          default keystone;
        }
        refine endpoint {
          default "http://localhost:5000/v2.0";
        }
      }
      container tenant {
        leaf id { type string; }
        leaf name { type string; }
      }
    }
    output {
      uses nfvi:common-action-output;
      leaf provider-id {
        type instance-identifier { /* ct:instance-type ResourceProvider; */ }
      }
    }
  }
}
