submodule openstack-nova {
  namespace "urn:ietf:params:xml:ns:yang:openstack-nova";
  belongs-to openstack-controller { prefix ostack; }
  yang-version 1.1;

  import opnfv-infrastructure { prefix nfvi; }

  revision 2016-07-07 {
    description
      "Updated to remove dependency to complex-types and adopt YANG 1.1";
  }
  
  identity nova { base nfvi:compute; }
  
  feature availability-zone {
    description "Specifies whether availability zone functionality is available.";
  }
  feature extended-status {
    description "Specifies whether extended status functionality is available.";
  }
  feature security-groups {
    description "Specifies whether security groups functionality is available.";
  }

  augment "/nfvi:controller/nfvi:compute" {
    list security-group {
      if-feature security-groups;
      uses nfvi:resource-element;
      // TBD
    }
  }
  
  augment "/nfvi:controller/nfvi:compute/nfvi:server" {
    leaf zone {
      if-feature availability-zone;
      type string;
    }
    container extended-status {
      if-feature extended-status;
      leaf locked-by;
      leaf power;
      leaf task;
      leaf vm;
    }
    leaf-list security-groups {
      if-feature security-groups;
      type leafref {
        path "../../security-group/id";
      }
    }

    // OpenStack Nova specific RPC calls
    action resize;
    action backup;
    action migrate;
    action restore;
    action evacuate;
    action lock;
    action unlock;
    action suspend;
    action resume;
    action pause;
    action unpause;
    action inject-network;
    action reset-network;
  }
}
