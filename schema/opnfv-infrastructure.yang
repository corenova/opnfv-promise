module opnfv-infrastructure {
  namespace "urn:ietf:params:xml:ns:yang:opnfv-infrastructure";
  prefix nfvi;
  yang-version 1.1;

  import ietf-inet-types { prefix inet; }
  import ietf-yang-types { prefix yang; }
  import yang-meta-types { prefix meta; }

  organization
    "Open Platform for NFV (OPNFV) / Corenova Technologies, Inc.";
  
  contact
    "Peter K. Lee <peter@corenova.com>";

  description
    "NFV Infrastructure Data Models representing the various
     ResourceElements available in the infrastructure across compute,
     network, and storage.

     Copyright (c) 2016 OPNFV and the persons identified as authors of
     the code.  All rights reserved.

     Redistribution and use in source and binary forms, with or
     without modification, is permitted pursuant to, and subject to
     the license terms of the Apache License, Version 2.0 which
     accompanies this distribution, and is available at
     (http://www.apache.org/licenses/LICENSE-2.0).";

  revision 2016-07-07 {
    description
      "Updated to remove dependency to complex-types and adopt YANG 1.1";
  }
  revision 2015-10-13 {
    description
      "Introduce capacity and element collection into NFVI models";
  }
  revision 2015-08-07 {
    description
      "This YANG module is modeled using 'yangforge' which natively provides
       complex types and typed instance identifiers. This module
       provides various collections of resource management data models
       for instance based management";
  }

  /*
   * Identities
   */
  identity controller {
    description "used by specific modules implementing controller role for NFVI";
  }
  identity release {
    base controller;
  }
  identity distro  {
    base controller;
  }
  identity compute {
    description "used by specific modules implementing compute role for NFVI";
    base controller;
  }
  /*
   * Type definitions
   */
  typedef unique-identifier {
    description "defines valid formats for external reference id";
    type union {
      type uint32;
      type yang:uuid;
      type inet:uri;
    }
  }
  /*
   * Groupings
   */
  grouping resource-element {
    description
      "A resource element represents access managed data entity.";
    leaf id {
      type unique-identifier;
      mandatory true;
    }
    leaf name {
      type string;
    }
    leaf description {
      type meta:description;
    }
    leaf enabled {
      type boolean;
      default true;
    }
    leaf protected {
      type boolean;
      default false;
    }
    leaf owner {
      type instance-identifier;
    }
    leaf visibility {
      description "Specify visibility level available from the perspective of 'owner'";
      type enumeration {
        enum public;
        enum domain;
        enum project;
        enum group;
        enum user;
      }
      default user;
    }
    leaf-list tags {
      type string;
    }
    leaf-list members {
      description "Optionally share with other identified entities";
      type instance-identifier;
    }
  }
  grouping resource-instance {
    uses nfvi:resource-element;
    leaf status {
      type enumeration {
        enum active;
        enum inactive;
        enum pending;
      }
    }
    leaf progress {
      type uint8 { range 0..100; }
      default 0;
    }
  }
  grouping compute-host {
    uses nfvi:resource-element;
    leaf type { type string; }
    leaf version { type string; }
    leaf cpu { type uint8; }
    leaf workload { type uint8; default 0; }
    leaf uptime { type string; }
    container ram {
      leaf total { type uint32; units 'MB'; }
      leaf used { type uint32; units 'MB'; }
      leaf free { type uint32; units 'MB'; }
    }
    container disk {
      leaf total { type uint32; units 'GB'; }
      leaf used { type uint32; units 'GB'; }
      leaf free { type uint32; units 'GB'; }
    }
    list hypervisor {
      key "id";
      uses nfvi:resource-element;
      container vcpu {
        leaf total { type uint16; }
        leaf used  { type uint16; }
        leaf free  { type uint16; }
      }
      leaf-list servers {
        type leafref {
          path "/nfvi:controller/nfvi:compute/nfvi:server/nfvi:id";
        }
      }
    }
  }
  grouping virtual-server {
    uses nfvi:resource-instance;
    leaf flavor {
      config false;
      type leafref {
        path "/nfvi:controller/compute/flavor/id";
      }
    }
    leaf image {
      config false;
      type leafref {
        path "/nfvi:controller/compute/image/id";
      }
    }
    leaf host {
      config false;
      type leafref {
        path "/nfvi:controller/compute/host/id";
      }
    }
    leaf metadata {
      type binary;
    }
    // leaf-list connections {
    //   description
    //     "References to collection of NetworkingElement class objects such as
    //      Network, Subnet, Port, Router that this ServerInstance is
    //      connected with.";
    //   type instance-identifier { ct:instance-type NetworkElement; }
    // }
  }
  grouping server-image {
    uses nfvi:resource-element;
    leaf checksum {
      type string;
      mandatory true;
    }
    leaf size {
      type uint32;
      units 'Bytes';
      mandatory true;
    }
    container format {
      leaf container {
        type enumeration { enum ami; enum ari; enum aki; enum bare; enum ovf; }
        default bare;
      }
      leaf disk {
        type enumeration { enum ami; enum ari; enum aki; enum vhd; enum vmdk; enum raw; enum qcow2; enum vdi; enum iso; }
        default raw;
      }
    }
    leaf content {
      description "should be a 'private' property so only direct access retrieves content";
      type union {
        type binary;
        type inet:uri;
      }
      mandatory true;
    }
    container constraint {
      leaf disk { type uint32; units 'GB'; default 0; }
      leaf ram  { type uint32; units 'MB'; default 0; }
      leaf vcpu { type uint16; default 0; }
    }
  }
  grouping resource-flavor {
    uses nfvi:resource-element;
    leaf disk  { type uint32; units 'GB'; default 0; }
    leaf ram   { type uint32; units 'MB'; default 0; }
    leaf vcpus { type uint16; default 0; }
  }

  /*
   * Configuration Data Nodes
   */
  container controller {
    description
      "Information model describing a NFVI resource stack comprising of
       various resource elements across compute, network, and storage";

    uses nfvi:resource-element;
    container compute {
      description
        "Contains compute related resources";
      list host {
        key id;
        uses nfvi:compute-host;
      }
      list server {
        key id;
        uses nfvi:virtual-server;
      }
      list image {
        key id;
        uses nfvi:server-image;
      }
      list flavor {
        key id;
        uses nfvi:resource-flavor;
      }
      action instantiate {
        input {
          leaf name {
            type string;
            mandatory true;
          }
          leaf flavor {
            type leafref {
              path "../../../flavor/id";
            }
            mandatory true;
          }
          leaf image {
            type leafref {
              path "../../../image/id";
            }
            mandatory true;
          }
          leaf-list networks {
            type leafref {
              path "/nfvi:controller/fabric/network/id";
            }
            description "optional, will assign default network if not provided";
          }
        }
        output {
          leaf server-id {
            type leafref {
              path "../../../server/id";
            }
          }
        }
      }
      action destroy {
        
      }
    }
    container fabric {
      description
        "Contains networking related resources";
      list network {
        key id;
        uses nfvi:resource-element;

        list subnet {
          key id;
          uses nfvi:resource-element;
          
          leaf-list nameservers {
            type string;
          }
          container dhcp {
            leaf enabled { type boolean; }
            list pool {
              leaf start { type inet:ip-address; }
              leaf end   { type inet:ip-address; }
            }
          }
          list port {
            key id;
            uses nfvi:resource-element;
            // TBD
          }
        }
      }
      list router {
        key id;
        uses nfvi:resource-instance;
        // TBD
      }
    }
    container storage {
      description
        "Contains storage related resources";
      // TBD
    }
  }
}
