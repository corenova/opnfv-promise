module openstack {
  prefix os;

  import nfv-infrastructure { prefix nfvi; }

  import openstack-identity { prefix os-id; }
  import openstack-compute { prefix os-com; }
  import openstack-network { prefix os-net; }
  import openstack-storage { prefix os-sto; }
  import complex-types { prefix ct; }

  identity openstack { base nfvi:manager; }
  identity release { base openstack; }
  identity distro { base openstack; }

  // OpenStack infrastructure platform
  container platform {
    uses nfvi:resource-stack {
      refine "compute/servers" { ct:instance-type os-com:ServerInstance; }
    }
    
    leaf release { type identityref { base release; } }
    leaf distro  { type identityref { base distro; } }
    
    ct:instance-list services { ct:instance-type OpenStackService; }
    ct:instance-list endpoints { ct:instance-type ServiceEndpoint; }

    container identity {
      choice version {
        case v3 {
          container auth {
          
          }
        }
      }
      ct:instance-list domains { ct:instance-type os-id:Domain; }
      ct:instance-list projects { ct:instance-type os-id:Project; }
      ct:instance-list users { ct:instance-type os-id:User; }
      ct:instance-list groups { ct:instance-type os-id:Group; }
    }
  }

  // OpenStack administrator configuration tree
  container admin {
    container auth {
      
    }
  }

  
}
