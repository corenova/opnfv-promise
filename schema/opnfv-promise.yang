module opnfv-promise {
  namespace "urn:ietf:params:xml:ns:yang:opnfv-promise";
  prefix promise;
  yang-version 1.1;

  import ietf-yang-types { prefix yang; }
  import ietf-inet-types { prefix inet; }
  import opnfv-infrastructure { prefix nfvi; }

  organization
    "Open Platform for NFV (OPNFV) / Corenova Technologies, Inc.";
  
  contact
    "Peter K. Lee <peter@corenova.com>";

  description
    "OPNFV Promise Resource Reservation/Allocation controller module

     Copyright (c) 2016 OPNFV and the persons identified as authors of
     the code.  All rights reserved.

     Redistribution and use in source and binary forms, with or
     without modification, is permitted pursuant to, and subject to
     the license terms of the Apache License, Version 2.0 which
     accompanies this distribution, and is available at
     (http://www.apache.org/licenses/LICENSE-2.0).";

  revision 2016-07-07 {
    description
      "Updated to remove dependency to complex-types and adopt YANG 1.1";
  }
  revision 2015-10-05 {
    description "Complete coverage of reservation related intents";
  }
  revision 2015-08-06 {
    description "Updated to incorporate YangForge framework";
  }
  revision 2015-04-16 {
    description "Initial revision.";
  }

  feature capacity-management {
    description "When available, provides capacity management service";
  }
  feature reservation-management {
    description "When available, provides reservation management service";
  }
  /*
   * Groupings
   */
  grouping compute-capacity {
    leaf cores     { type int16; default 0; }
    leaf ram       { type int32; default 0; units 'MB'; }
    leaf instances { type int16; default 0; }
  }
  grouping network-capacity {
    leaf networks  { type int16; default 0; }
    leaf ports     { type int16; default 0; }
    leaf routers   { type int16; default 0; }
    leaf subnets   { type int16; default 0; }
    leaf addresses { type int32; default 0; }
  }
  grouping storage-capacity {
    leaf gigabytes { type int32; default 0; units 'GB'; }
    leaf snapshots { type int16; default 0; }
    leaf volumes   { type int16; default 0; }
  }
  grouping resource-capacity {
    uses promise:compute-capacity;
    uses promise:network-capacity;
    uses promise:storage-capacity;
  }
  grouping resource-collection {
    description
      "Information model capturing parameters for describing a collection of
       resource capacity and resource elements";
    container capacity {
      uses promise:resource-capacity;
    }
    leaf-list elements {
      type instance-identifier {
        //ct:instance-type nfvi:ResourceElement;
        require-instance true;
      }
    }
  }
  grouping time-window {
    description
      "Describes a time bound start/end where start <= end";
    leaf start { type yang:date-and-time; }
    leaf end   { type yang:date-and-time; }
  }
  grouping temporal-resource-element {
    description
      "Describes a time bound resource element data model, which represents a
       temporal resource only available during a given window in time.";
    uses nfvi:resource-element;
    uses promise:time-window;
    leaf active {
      config false;
      description
        "Provides current state of this element whether it is enabled and
         within specified start/end time";
      type boolean;
    }
  }
  grouping resource-usage-request {
    description
      "Information model capturing available parameters to make a resource
       usage request.";
    reference "OPNFV-PROMISE, Section 3.4.1";
    uses promise:time-window;
    leaf zone {
      description "Optional identifier to an Availability Zone";
      type instance-identifier;
    }
    choice strategy {
      case bulk-quantity-request {
        description
          "The bulk-quantity-request usage strategy will perform a capacity
           quantity based reservation along with an optional reference
           to a list of *pre-existing* elements required for
           fulfilling the reservation.

           If the resource-usage-request is accepted, the referenced
           elements will be placed into 'protected' mode as to prevent
           accidental removal. If any of these reserved resource
           elements become 'unavailable' due to environmental or
           administrative activity, a notification will be issued
           informing of the issue.";
        uses promise:resource-collection;
      }
      case flavor-quantity-request {
        description
          "The flavor-quantity-request usage strategy will perform a reservation
           based on explicit references to currently available flavors
           and the number of such flavors that will be needed in the
           future.

           This form of resource-usage-request will factor in
           available resource capacity on a per hypervisor basis in
           addition to the projected total available capacity that
           will be available in the requested start/end time window.

           If the resource-usage-request is accepted, the required
           hypervisor resource elements will be placed into
           'protected' mode as to prevent accidental
           removal. Furthermore, if any of the reserved hypervisor
           resource elements are no longer able to satisfy the
           instantiation requirements, a notification will be issued
           informing of the issue.";
        list instance {
          key 'flavor';
          leaf flavor {
            type leafref {
              path "/nfvi:controller/compute/flavor/id";
            }
          }
          leaf count {
            type uint16 {
              range 1..max;
            }
            mandatory true;
          }
        }
      }
    }
  }
  grouping query-resource-collection {
    container window {
      description "Matches entries that are within the specified start/end time window";
      leaf start { type yang:date-and-time; }
      leaf end   { type yang:date-and-time; }
      leaf scope {
        type enumeration {
          enum "exclusive" {
            description "Matches entries that start AND end within the window";
          }
          enum "inclusive" {
            description "Matches entries that start OR end within the window";
          }
        }
        default "inclusive";
      }
    }
    leaf-list without {
      description "Excludes specified collection identifiers from the result";
      type instance-identifier;
    }
    leaf show-utilization { type boolean; default true; }
    container elements {
      leaf-list some {
        description "Query for ResourceCollection(s) that contain some or more of these element(s)";
        type instance-identifier;
      }
      leaf-list every {
        description "Query for ResourceCollection(s) that contain all of these element(s)";
        type instance-identifier;
      }
    }
  }
  grouping utilization-output {
    list utilization {
      key 'timestamp';
      leaf timestamp { type yang:date-and-time; }
      leaf count { type int16; }
      container capacity { uses promise:resource-capacity; }
    }
  }
  grouping common-action-output {
    leaf result {
      type enumeration {
        enum "ok";
        enum "conflict";
        enum "error";
      }
    }
    leaf message { type string; }
  }
  grouping reservations-list {

    list pool {
      description
        "Each entry describes available capacity and elements for a given time window";
      key "id";
      uses promise:temporal-resource-element;
      uses promise:resource-collection;
    }
    list reservation {
      description
        "Each entry Describes an accepted resource reservation request, created
         usually as a result of 'reserve' action.

         A ResourceReservation is a derived instance of a generic
         ResourceCollection which has additional parameters to map the
         pool(s) that were referenced to accept this reservation as well
         as to track allocations made referencing this reservation.

         Contains the capacities of various resource attributes being
         reserved along with any resource elements that are needed to be
         available at the time of allocation(s).";
    
      reference "OPNFV-PROMISE, Section 3.4.1";

      key "id";
      uses promise:temporal-resource-element;
      uses promise:resource-collection;
      container remaining {
        config false;
        description
          "Provides visibility into total remaining capacity for this
           reservation based on allocations that took effect utilizing
           this reservation ID as a reference.";
        uses promise:resource-capacity;
      }
      leaf-list pools {
        config false;
        description
          "Provides list of one or more pools that were referenced for providing
           the requested resources for this reservation.  This is an
           important parameter for informing how/where allocation
           requests can be issued using this reservation since it is
           likely that the total reserved resource capacity/elements are
           made availble from multiple sources.";
        type leafref {
          path "../../pool/id";
        }
      }
      leaf-list allocations {
        config false;
        description
          "Reference to a collection of consumed allocations referencing
           this reservation.";
        type leafref {
          path "/nfvi:controller/nfvi:compute/nfvi:server/nfvi:id";
        }
      }
      leaf created-on  {
        config false;
        type yang:date-and-time;
      }
      leaf modified-on {
        config false;
        type yang:date-and-time;
      }
      action validate {
        
      }
      action update {
        description "Update reservation details for an existing reservation";
        input {
          uses promise:resource-usage-request;
        }
        output {
          uses promise:common-action-output;
        }
      }
      notification failure {
        description "Notify when failure occurs for an existing reservation";
      }
    }
  }
  /*
   * Configuration data nodes
   */
  container admin {
    description
      "Administrative configuration for managing the Promise module";
    container policy {
      leaf max-future-start-range {
        description
          "Enforce reservation request 'start' time is within allowed range from now";
        type uint16 { range 0..365; }
        units "days";
      }
      leaf max-future-end-range {
        description
          "Enforce reservation request 'end' time is within allowed range from now";
        type uint16 { range 0..365; }
        units "days";
      }
      leaf max-duration {
        description
          "Enforce reservation duration (end-start) does not exceed specified threshold";
        type uint16;
        units "hours";
        default 8760; // for now cap it at max one year as default
      }
      leaf expiry {
        description
          "Duration in minutes from start when unallocated reserved resources
           will be released back into the pool";
        type uint32;
        units "minutes";
      }
    }
  }
  /*
   * Augmentations to NFVI module
   * Extends nfvi module with capacity and reservation facilities
   */
  augment "/nfvi:controller" {
    container capacity {
      config false;
      description "Describes current state info about capacity utilization info";
      container total     { uses promise:resource-capacity; }
      container reserved  { uses promise:resource-capacity; }
      container usage     { uses promise:resource-capacity; }
      container available { uses promise:resource-capacity; }
      
      leaf-list elements {
        description "aggregate reference to all resource-element identifiers";
        type instance-identifier;
      }
      uses promise:reservations-list;
      
      action increase {
        description "Increase total capacity available for reservations between a window in time";
        input {
          uses promise:time-window;
          uses promise:resource-capacity;
        }
        output {
          uses promise:common-action-output;
          leaf pool-id {
            type leafref {
              path "../../../pool/id";
            }
          }
        }
      }
      action decrease {
        description "Decrease total capacity available for reservations between a window in time";
        input {
          uses promise:time-window;
          uses promise:resource-capacity;
        }
        output {
          uses promise:time-window;
          uses promise:common-action-output;
          leaf pool-id {
            type leafref {
              path "../../../pool/id";
            }
          }
        }
      }
      action reserve {
        description "Make a request to reserve resources";
        input {
          uses promise:resource-usage-request;
        }
        output {
          uses promise:common-action-output;
          leaf reservation-id {
            type leafref {
              path "../../../reservation/id";
            }
          }
        }
      }
      action query {
        description "Check capacity information about a specified resource collection";
        input {
          leaf capacity {
            type enumeration {
              enum 'total';
              enum 'reserved';
              enum 'usage';
              enum 'available';
            }
            default 'available';
          }
          leaf zone { type string; }
          uses promise:query-resource-collection;
          // TBD: additional parameters for query-capacity
        }
        output {
          leaf-list records { type instance-identifier; }
          uses promise:utilization-output;
        }
      }
    }
  }
  augment "/nfvi:controller/nfvi:compute" {
    container capacity {
      if-feature capacity-managment;
      uses promise:compute-capacity;
    }
  }
  augment "/nfvi:controller/nfvi:fabric" {
    container capacity {
      if-feature capacity-managment;
      uses promise:network-capacity;
    }
  }
  augment "/nfvi:controller/nfvi:storage" {
    container capacity {
      uses promise:storage-capacity;
    }
  }
  augment "/nfvi:controller/nfvi:compute/nfvi:server" {
    description
      "A ResourceAllocation record denotes consumption of resources from a
       referenced ResourcePool.

       It does not reflect an accepted request but is created to
       represent the actual state about the ResourcePool. It is
       created once the allocation(s) have successfully taken effect
       on the 'source' of the ResourcePool.
       
       The 'priority' state indicates the classification for dealing
       with resource starvation scenarios. Lower priority allocations
       will be forcefully terminated to allow for higher priority
       allocations to be fulfilled.

       Allocations without reference to an existing reservation will
       receive the lowest priority.";
    
    reference "OPNFV-PROMISE, Section 3.4.3";

    leaf reservation-id {
      config false;
      description "Reference to an existing reservation identifier (if specified during instantiate)";
      type leafref {
        path "/nfvi:controller/promise:capacity/promise:reservation/promise:id";
      }
    }
    leaf priority {
      config false;
      description
        "Reflects current priority level of the allocation according to classification rules";
      type enumeration {
        enum "high"   { value 1; }
        enum "normal" { value 2; }
        enum "low"    { value 3; }
      }
      default "normal";
    }
  }
  augment "/nfvi:controller/nfvi:compute/nfvi:instantiate/nfvi:input" {
    leaf reservation-id {
      description "An optional reference to an existing reservation";
      type leafref {
        path "/nfvi:controller/promise:capacity/promise:reservation/promise:id";
      }
    }
  }
}
