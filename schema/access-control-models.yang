module access-control-models {
  yang-version 1.1;
  namespace "urn:opnfv:promise:acm";
  prefix acm;

  import ietf-yang-types { prefix yang; }
  import ietf-inet-types { prefix inet; }

  revision 2016-07-07 {
    description
      "Updated to remove dependency to complex-types and adopt YANG 1.1";
  }
  
  typedef password {
    type string {
      length 1..255;
    }
  }

  typedef unique-identifier {
    description "defines valid formats for external reference id";
    type union {
      type uint32;
      type yang:uuid;
      type inet:uri;
    }
  }

  grouping access-credentials {
    leaf strategy {
      type enumeration {
        enum oauth;
      }
      default oauth;
    }
    leaf endpoint {
      type inet:uri;
      description "The target endpoint for authentication";
      mandatory true;
    }
    leaf username {
      type string;
      mandatory true;
    }
    leaf password {
      type acm:password;
      mandatory true;
    }
  }
  
  grouping access-identity {
    description "Identity represents an administrative access model entity";

    leaf id { type unique-identifier; mandatory true; }
    leaf name { type string; }
    leaf description { type string; }
    leaf enabled { type boolean; default true; }
  }

  grouping access-domain {
    uses access-identity;
    
    description
      "Domain represent a distinct administrative domain across
       collection of users and groups.";

    list user {
      uses access-identity;
      
      leaf credential {
        type string;
        mandatory true;
      }
    
      leaf fullName { type string; }
      leaf email { type string; }
      
      leaf-list groups {
        type leafref {
          path "../../group/id";
        }
      }
      leaf domain {
        config false;
        type leafref {
          path "../../id";
        }
      }
      action create;
      action remove;
    }
    list group {
      uses access-identity;
      leaf-list users {
        type leafref {
          path "../../user/id";
        }
      }
      leaf domain {
        config false;
        type leafref {
          path "../../id";
        }
      }
      action create;
      action remove;
    }
  }
}
