module openstack-resource-provider {

  belongs-to openstack { prefix os; }

  import storm-management-models { prefix smm; }
  import storm-resource-models { prefix srm; }
  import complex-types { prefix ct; }

  include openstack-server-instance;
  
  identity openstack { base "srm:resource-provider"; }
  identity release { base "openstack"; }
  identity distro { base "openstack"; }

  feature availability-zone {
    description "Specifies whether availability zone functionality is available.";
  }
  feature extended-status {
    description "Specifies whether extended status functionality is available.";
  }
  feature security-groups {
    description "Specifies whether security groups functionality is available.";
  }
  
  ct:complex-type OpenStackResourceProvider {
    ct:extends srm:ResourceProvider;

    leaf release { type identityref { base "release"; } }
    leaf distro  { type identityref { base "distro"; } }
    
    
    // NOTE: unsure whether services and endpoints are needed
    ct:instance-list services { ct:instance-type OpenStackService; }
    ct:instance-list endpoints { ct:instance-type ServiceEndpoint; }

    augment "auth" {
      ct:instance-list tokens { ct:instance-type smm:AuthorizationToken; }
    }

    refine "compute/servers" { ct:instance-type OpenStackServerInstance; }
    refine "networking/networks" { ct:instance-type OpenStackNetwork; }
  }

  // Various RPC extensions available on the openstack-resource-provider
    
  rpc list-servers {
    input {
      leaf provider { type instance-type { ct:instance-type OpenStackResourceProvider; } }
    }
    output {
      ct:instance-list servers { ct:instance-type OpenStackServerInstance; }
    }
  }
  rpc create-server;
  
}
