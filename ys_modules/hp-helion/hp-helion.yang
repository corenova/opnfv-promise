module hp-helion {
  prefix hph;

  import openstack { prefix ostack; }

  identity hp-helion { base "ostack:distro"; }

  feature hp-helion-mgmt {
    description
      "Provide additional capabilities to manage extra services.";
  }
  

  
  ct:complex-type Helion {
    ct:extends ostack:ResourceProvider;

    
    
  }

  container hp-helion-mgmt {
    if-feature hp-helion-mgmt;

    leaf uptime {
      config false;
      type string;
    }

    
    
  }
}
