submodule opnfv-abstract-models {

  belongs-to opnfv-vim { prefix vim; }
  
  import yang-storm { prefix ys; }
  
  /*********************************************
   * Abstract Models (must be subclassed)
   *********************************************/

  ys:complex-type AccessIdentity {
    ys:extends ys:DataModel;
    ys:abstract true;
    
    description "AccessIdentity represents an administrative access model entity";
    leaf name { type string; mandatory true; }
    leaf description { type string; }
    leaf enabled { type boolean; default true; }
  }

  ys:complex-type ResourceElement {
    ys:extends ys:DataModel;
    ys:abstract true;
    
    leaf name { type string; mandatory true; }
    leaf enabled { type boolean; default true; }
    leaf protected { type boolean; default false; }
    leaf owner { type instance-identifier { ys:instance-type AccessIdentity; } }
    leaf visibility {
      description "Specify visibility level available from the perspective of 'owner'";
      type enumeration {
        enum public;
        enum domain;
        enum project;
        enum group;
        enum user;
      }
      default user;
    }
    leaf-list tags { type string; }
    
    leaf-list members {
      description "Optionally share with explicit list of members of AccessIdentity complex-type";
      type instance-identifier {
        ys:instance-type AccessIdentity;
      }
    }
  }

  ys:complex-type ResourceInstance {
    ys:extends ResourceElement;
    ys:abstract true;

    leaf status {
      type enumeration {
        enum active;
        enum inactive;
        enum pending;
      }
    }
    leaf progress { type number; default 0; }
  }
}
