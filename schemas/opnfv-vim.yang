module opnfv-vim {
  prefix vim;

  import yang-storm { prefix ys; }

  include opnfv-abstract-models { ys:source 'opnfv-abstract-models.yang'; }
  include opnfv-identity-models { ys:source 'opnfv-identity-models.yang'; }
  include opnfv-compute-models  { ys:source 'opnfv-compute-models.yang'; }
  include opnfv-network-models  { ys:source 'opnfv-network-models.yang'; }
  //include opnfv-storage-modesl  { ys:source 'opnfv-storage-models.yang'; }
  include opnfv-promise-models  { ys:source 'opnfv-promise-models.yang'; }

  /*********************************************
   * Abstract Models (must be subclassed)
   *********************************************/
  
  grouping resource-capacity {
    container capacity {
      container quota { description 'Conceptual container that should be extended'; }
      container usage { description 'Conceptual container that should be extended'; config false; }
      container reserved { description 'Conceptual container that should be extended'; config false; }
      container available { description 'Conceptual container that should be extended'; config false; }
    }
  }

  ys:complex-type ResourceProvider {
    ys:abstract true;
    
    leaf name { type string; mandatory true; }

    ys:instance-list domains { ys:instance-type ResourceDomain; }
    ys:instance-list projects { ys:instance-type DomainProject; }
    ys:instance-list users { ys:instance-type DomainUser; }
    ys:instance-list groups { ys:instance-type DomainGroup; }
    
    container auth {
      description 'Conceptual container that will be extended by explicit provider';
      // ys:instance-list credentials { ys:instance-type AccessCredential; }
      // ys:instance-list roles { ys:instance-type AccessRole; }
      // ys:instance-list policies { ys:instance-type AccessPolicy; }
    }

    ys:instance-list hosts { ys:instance-type PhysicalHost; }
    ys:instance-list hypervisors { ys:instance-type Hypervisor; }

    container compute {
      if-feature has-compute;
      description "Contains compute related resources";

      ys:instance-list servers { ys:instance-type ServerInstance; }
      ys:instance-list images { ys:instance-type VirtualMachineImage; }
      ys:instance-list flavors { ys:instance-type VirtualMachineFlavor; }

      uses resource-capacity {
        if-feature has-compute-capacity;
        augment "capacity/quota" { uses compute-capacity; }
        augment "capacity/usage" { uses compute-capacity; }
        augment "capacity/reserved" { uses compute-capacity; }
        augment "capacity/available" { uses compute-capacity; }
      }
    }

    container networking {
      if-feature has-networking;
      description "Contains networking related resources";
        
      ys:instance-list networks { ys:instance-type Network; }
      ys:instance-list subnets { ys:instance-type SubNetwork; }
      ys:instance-list ports { ys:instance-type SwitchPort; }
      ys:instance-list routers { ys:instance-type Router; }

      uses resource-capacity {
        if-feature has-networking-capacity;
        augment "capacity/quota" { uses networking-capacity; }
        augment "capacity/usage" { uses networking-capacity; }
        augment "capacity/reserved" { uses networking-capacity; }
        augment "capacity/available" { uses networking-capacity; }
      }
    }

    ys:instance-list reservations {
      if-feature resource-reservation;
      ys:instance-type ResourceReservation;
    }
    
    rpc list-servers;
    rpc create-server;
    rpc destroy-server;
    rpc reboot-server;
  }
  
  /*********************************************
   * ResourceElement Models
   *********************************************/

  ys:complex-type PhysicalHost {
    ys:extends ResourceElement;

    leaf type { type string; }
    leaf version { type string; }

    leaf cpu { type number; }
    leaf workload { type number; default 0; }
    leaf uptime { type string; }

    container ram {
      leaf total { type number; units 'MB'; }
      leaf used { type number; units 'MB'; }
      leaf free { type number; units 'MB'; }
    }
    container disk {
      leaf total { type number; units 'GB'; }
      leaf used { type number; units 'GB'; }
      leaf free { type number; units 'GB'; }
    }

    leaf-list hypervisors { type instance-identifier { ys:instance-type Hypervisor; } }

    rpc reboot;
    rpc shutdown;
    rpc startup;
  }
  
  ys:complex-type Hypervisor {
    ys:extends PhysicalHost;

    leaf host {
      type instance-identifier { ys:instance-type PhysicalHost; }
      mandatory true;
    }
    container vcpu {
      leaf total { type number; }
      leaf used { type number; }
      leaf free { type number; }
    }
    leaf-list servers { type instance-identifier { ys:instance-type ServerInstance; } }

    rpc evacuate;
  }
  
}
