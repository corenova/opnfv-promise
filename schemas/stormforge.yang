module stormforge {
  namespace "http://github.com/stormstack/stormforge";
  prefix sf;

  import yang-storm { prefix ys; }
  import opnfv-vim { prefix vim; ys:source 'opnfv-vim.yang'; }

  description
    "Virtualized Infrastructure Manager Data Models with complex types and
typed instance identifiers representing Resource providers, pools,
capacities, reservations, etc.";
  
  revision 2015-03-16 {
    description
      "The 'stormforge' YANG module is modeled using 'yang-storm'
which natively provides complex types and typed instance identifiers.
This module provides various collections of data models defined in
'opnfv-vim' schema for instance based management";
  }

  feature multi-provider {
    description "If supported, the endpoint can be used manage one or more resource providers";
  }

  // MAIN CONTAINER

  container stormforge {
    description "Top-level node of the stormforge data model";
    
    ys:instance-list resourceProviders {
      if-feature multi-provider;
      description "Aggregate collection of all registered ResourceProvider instances";
      ys:instance-type vim:ResourceProvider;
    }

    ys:instance-list resourceReservations {
      description "Aggregate collection of all registered ResourceReservation instances";
      ys:instance-type vim:ResourceReservation;
    } 
  }
  
  rpc list-providers;
  rpc add-provider;
  rpc remove-provider;

  rpc list-reservations;
  rpc create-reservation;
  rpc cancel-reservation;
}
