module openstack-vim {
  prefix osvim;
  
  import yang-storm { prefix ys; }
  import opnfv-vim { prefix vim; }

  ys:complex-type OpenStack {
    ys:extends vim:ResourceProvider;

    // NOTE: unsure whether services and endpoints are needed
    ys:instance-list services { ys:instance-type OpenStackService; }
    ys:instance-list endpoints { ys:instance-type ServiceEndpoint; }

    augment "auth" {
      ys:instance-list tokens { ys:instance-type vim:AuthorizationToken; }
    }

    refine "compute/servers" { ys:instance-type OpenStackServerInstance; }
    refine "networking/networks" { ys:instance-type OpenStackNetwork; }
  }

  ys:complex-type OpenStackServerInstance {
    ys:extends vim:ServerInstance;

    leaf zone {
      if-feature os-availability-zone;
      type string;
    }

    container extended-status {
      if-feature os-extended-status;
      leaf locked-by;
      leaf power;
      leaf task;
      leaf vm;
    }

    leaf-list security-groups {
      type instance-identifier { ys:instance-type SecurityGroup; }
    }
    
    // Various RPC extensions available on the ServerInstance

    rpc resize;
    rpc reboot;
    
    rpc backup;
    rpc migrate;
    rpc restore;
    rpc evacuate;
    
    rpc lock;
    rpc unlock;

    rpc suspend;
    rpc resume;

    rpc pause;
    rpc unpause;
    
    rpc inject-network;
    rpc reset-network;
  }
}
