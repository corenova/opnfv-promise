submodule opnfv-network-models {

  belongs-to opnfv-vim { prefix vim; }
  
  import yang-storm { prefix ys; }

  feature has-networking;
  feature has-networking-capacity;

  grouping networking-capacity {
    leaf network { type number; }
    leaf port { type number; }
    leaf router { type number; }
    leaf subnet { type number; }
    leaf address { type number; }
  }

  /*********************************************
   * Network Models (Work-in-Progress)
   *********************************************/

  ys:complex-type NetworkingElement {
    ys:extends vim:ResourceElement;
    ys:abstract true;

    
  }

  ys:complex-type Network {
    ys:extends NetworkingElement;

    leaf-list subnets {
      type instance-identifier { ys:instance-type SubNetwork; }
    }
  }

  ys:complex-type SubNetwork {
    ys:extends NetworkingElement;

    leaf network { type instance-identifier { ys:instance-type Network; } }

    leaf-list nameservers { type string; }
    
    container dhcp {
      leaf enabled { type boolean; }
      list pools {
        leaf start { type ip-address; }
        leaf end { type ip-address; }
      }
    }
  }

  ys:complex-type SwitchPort {
    ys:extends NetworkingElement;

    leaf subnet { type instance-identifier { ys:instance-type SubNetwork; } }
  }
}
