submodule opnfv-compute-models {

  belongs-to opnfv-vim { prefix vim; }
  
  import yang-storm { prefix ys; }

  feature has-compute;
  feature has-compute-capacity;
  
  grouping compute-capacity {
    leaf cores { type number; }
    leaf ram { type number; }
    leaf instances { type number; }
  }

  /*********************************************
   * Compute Models
   *********************************************/

  ys:complex-type ComputeElement {
    ys:extends vim:ResourceElement;
    ys:abstract true;

    container constraint {
      leaf disk { type number; units 'GB'; default 0; }
      leaf ram { type number; units 'MB'; default 0; }
      leaf vcpu { type number; default 0; }
    }

    leaf-list instances {
      description "State info about instances currently using this resource element";
      type instance-identifier {
        ys:instance-type vim:ResourceInstance;
      }
      config false;
    }
  }

  ys:complex-type VirtualMachineImage {
    ys:extends vim:ComputeElement;

    container data {
      leaf checksum { type string; mandatory true; }
      leaf size { type number; units 'Bytes'; mandatory true; }
      
      container format {
        leaf container {
          type enumeration { enum ami; enum ari; enum aki; enum bare; enum ovf; }
          default bare;
        }
        leaf disk {
          type enumeration { enum ami; enum ari; enum aki; enum vhd; enum vmdk; enum raw; enum qcow2; enum vdi; enum iso; }
        }
      }
    }

    rpc upload {
      description "uploads binary image data";
    }
    rpc download {
      description "downloads binary image data";
    }
  }

  ys:complex-type VirtualMachineFlavor {
    ys:extends vim:ComputeElement;
  }

  ys:complex-type ServerInstance {
    ys:extends vim:ResourceInstance;

    leaf project {
      type instance-identifier { ys:instance-type vim:DomainProject; }
      mandatory true;
    }
    leaf flavor {
      type instance-identifier { ys:instance-type VirtualMachineFlavor; }
      mandatory true;
    }
    leaf image {
      type instance-identifier { ys:instance-type VirtualMachineImage; }
      mandatory true;
    }
    ys:instance metadata { ys:instance-type MetaData; }

    leaf host {
      type instance-identifier { ys:instance-type vim:PhysicalHost; }
    }

    leaf-list links {
      description
        "References to collection of NetworkingElement class objects such as
         Network, Subnet, Port, Router that this ServerInstance is
         connected with.";
      type instance-identifier { ys:instance-type vim:NetworkingElement; }
    }
  }
}
