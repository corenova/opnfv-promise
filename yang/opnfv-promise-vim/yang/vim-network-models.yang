submodule vim-network-models {

  belongs-to opnfv-promise-vim { prefix vim; }

  /*********************************************
   * Network Models (Work-in-Progress)
   *********************************************/

  import complex-types { prefix ct; }

  ct:complex-type NetworkingElement {
    ct:extends vim:ResourceElement;
    ct:abstract true;
  }

  ct:complex-type Network {
    ct:extends NetworkingElement;

    leaf-list subnets {
      type instance-identifier { ct:instance-type SubNetwork; }
    }
  }

  ct:complex-type SubNetwork {
    ct:extends NetworkingElement;

    leaf network { type instance-identifier { ct:instance-type Network; } }

    leaf-list nameservers { type string; }
    
    container dhcp {
      leaf enabled { type boolean; }
      list pools {
        leaf start { type ip-address; }
        leaf end { type ip-address; }
      }
    }
  }

  ct:complex-type SwitchPort {
    ct:extends NetworkingElement;

    leaf subnet { type instance-identifier { ct:instance-type SubNetwork; } }
  }
}
