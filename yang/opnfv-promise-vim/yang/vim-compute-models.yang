submodule vim-compute-models {

  belongs-to opnfv-promise-vim { prefix vim; }

  organization
    "ClearPath Networks R&D Group";

  contact
    "Web:  <http://www.clearpathnet.com>
     Author: Peter K. Lee <mailto:plee@clearpathnet.com>";

  identity compute { base "resource"; }
  identity vm-image { base "compute"; }
  identity vm-flavor { base "compute"; }

  feature has-compute;

  /*********************************************
   * Compute Models
   *********************************************/

  import complex-types { prefix ct; }

  ct:complex-type ComputeElement {
    ct:extends vim:ResourceElement;
    ct:abstract true;

    container constraint {
      leaf disk { type number; units 'GB'; default 0; }
      leaf ram { type number; units 'MB'; default 0; }
      leaf vcpu { type number; default 0; }
    }

    leaf-list instances {
      description "State info about instances currently using this resource element";
      type instance-identifier {
        ct:instance-type vim:ResourceInstance;
      }
      config false;
    }
  }

  ct:complex-type VirtualMachineImage {
    ct:extends ComputeElement;

    container data {
      leaf checksum { type string; mandatory true; }
      leaf size { type number; units 'Bytes'; mandatory true; }
      
      container format {
        leaf container {
          type enumeration { enum ami; enum ari; enum aki; enum bare; enum ovf; }
          default bare;
        }
        leaf disk {
          type enumeration { enum ami; enum ari; enum aki; enum vhd; enum vmdk; enum raw; enum qcow2; enum vdi; enum iso; }
        }
      }
    }
  }

  ct:complex-type VirtualMachineFlavor {
    ct:extends ComputeElement;
  }

  ct:complex-type ServerInstance {
    ct:extends vim:ResourceInstance;

    leaf project {
      type instance-identifier { ct:instance-type vim:DomainProject; }
      mandatory true;
    }
    leaf flavor {
      type instance-identifier { ct:instance-type VirtualMachineFlavor; }
      mandatory true;
    }
    leaf image {
      type instance-identifier { ct:instance-type VirtualMachineImage; }
      mandatory true;
    }
    ct:instance metadata { ct:instance-type MetaData; }

    leaf host {
      type instance-identifier { ct:instance-type PhysicalHost; }
    }

    leaf-list links {
      description
        "References to collection of NetworkingElement class objects such as
         Network, Subnet, Port, Router that this ServerInstance is
         connected with.";
      type instance-identifier { ct:instance-type vim:NetworkElement; }
    }
  }

  ct:complex-type PhysicalHost {
    ct:extends vim:ResourceElement;

    leaf type { type string; }
    leaf version { type string; }

    leaf cpu { type number; }
    leaf workload { type number; default 0; }
    leaf uptime { type string; }

    container ram {
      leaf total { type number; units 'MB'; }
      leaf used { type number; units 'MB'; }
      leaf free { type number; units 'MB'; }
    }
    container disk {
      leaf total { type number; units 'GB'; }
      leaf used { type number; units 'GB'; }
      leaf free { type number; units 'GB'; }
    }

    leaf-list hypervisors { type instance-identifier { ct:instance-type Hypervisor; } }
  }
  
  ct:complex-type Hypervisor {
    ct:extends PhysicalHost;

    leaf host {
      type instance-identifier { ct:instance-type PhysicalHost; }
      mandatory true;
    }
    container vcpu {
      leaf total { type number; }
      leaf used { type number; }
      leaf free { type number; }
    }
    leaf-list servers { type instance-identifier { ct:instance-type ServerInstance; } }
  }

  rpc image-upload {
    description "uploads binary image data";
  }
  rpc image-download {
    description "downloads binary image data";
  }
  
  rpc host-reboot;
  rpc host-shutdown;
  rpc host-startup;

  rpc hypervisor-evacuate;
}
