submodule vim-abstract-models {

  belongs-to opnfv-promise-vim { prefix vim; }
  
  import opnfv-management-models { prefix mgmt; }
  import complex-types { prefix ct; }
  
  /*********************************************
   * Abstract Models (must be subclassed)
   *********************************************/

  ct:complex-type ResourceElement {
    ct:abstract true;

    key "id";
    leaf id { type uuid; mandatory true; default auto; }
    leaf name { type string; mandatory true; }
    leaf enabled { type boolean; default true; }
    leaf protected { type boolean; default false; }
    leaf owner { type instance-identifier { ct:instance-type mgmt:Identity; } }
    leaf visibility {
      description "Specify visibility level available from the perspective of 'owner'";
      type enumeration {
        enum public;
        enum domain;
        enum project;
        enum group;
        enum user;
      }
      default user;
    }
    leaf-list tags { type string; }
    
    leaf-list members {
      description "Optionally share with explicit list of members of AccessIdentity complex-type";
      type instance-identifier {
        ct:instance-type mgmt:Identity;
      }
    }
  }

  ct:complex-type ResourceInstance {
    ct:extends ResourceElement;
    ct:abstract true;

    leaf status {
      type enumeration {
        enum active;
        enum inactive;
        enum pending;
      }
    }
    leaf progress { type number; default 0; }
  }
}
