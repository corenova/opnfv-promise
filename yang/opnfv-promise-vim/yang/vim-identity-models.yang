submodule vim-identity-models {

  belongs-to opnfv-promise-vim { prefix vim; }
  
  import opnfv-management-models { prefix mgmt; }
  import complex-types { prefix ct; }
  
  /*********************************************
   * AccessIdentity Models
   *********************************************/

  ct:complex-type ResourceDomain {
    ct:extends mgmt:Domain;
    description
      "ResourceDomain represent a distinct administrative domain across including projects.";
    
    leaf-list projects { type instance-identifier { ct:instance-type ResourceProject; } }
  }

  ct:complex-type ResourceProject {
    ct:extends mgmt:DomainIdentity;
    description
      "DomainProject represent a distinct resource consumption space across
       collection of users and groups that can reserve and allocate
       resources.";
    
    leaf-list users { type instance-identifier { ct:instance-type ResourceUser; } }
    leaf-list groups { type instance-identifer { ct:instance-type mgmt:DomainGroup; } }

    container resource {
      leaf-list images {
        if-feature vm-images;
        type instance-identifier { ct:instance-type vim:VirtualMachineImage; }
      }

      leaf-list flavors {
        if-feature compute-flavors;
        type instance-identifier { ct:instance-type vim:VirtualMachineFlavor; }
      }
    }
  }

  ct:complex-type ResourceUser {
    ct:extends mgmt:DomainUser;

    leaf-list projects { type instance-identifier { ct:instance-type ResourceProject; } }
  }
}
