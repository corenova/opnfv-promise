module opnfv-promise-vim {
  namespace "urn:opnfv:promise:vim";
  prefix vim;

  include vim-abstract-models;
  include vim-identity-models;
  include vim-compute-models;
  include vim-network-models;
  //include vim-storage-models;

  import opnfv-management-models { prefix mgmt; }
  import complex-types { prefix ct; }

  description
    "Virtualized Infrastructure Manager Data Models with complex types and
     typed instance identifiers representing Resource providers, 
     domains, projects, compute, network, storage, etc.";
  
  revision 2015-08-07 {
    description
      "The 'opnfv-promise-vim' YANG module is modeled using 'yangforge' which
       natively provides complex types and typed instance identifiers.
       This module provides various collections of resource management
       data models for instance based management";
  }
  
  ct:complex-type ResourceProvider {
    ct:abstract true;
    
    leaf name { type string; mandatory true; }

    ct:instance-list domains { ct:instance-type ResourceDomain; }
    ct:instance-list projects { ct:instance-type ResourceProject; }
    ct:instance-list users { ct:instance-type mgmt:DomainUser; }
    ct:instance-list groups { ct:instance-type mgmt:DomainGroup; }
    
    container auth {
      description 'Conceptual container that will be extended by explicit provider';
      // ct:instance-list credentials { ct:instance-type AccessCredential; }
      // ct:instance-list roles { ct:instance-type AccessRole; }
      // ct:instance-list policies { ct:instance-type AccessPolicy; }
    }

    ct:instance-list hosts { ct:instance-type PhysicalHost; }
    ct:instance-list hypervisors { ct:instance-type Hypervisor; }

    container compute {
      if-feature has-compute;
      description "Contains compute related resources";

      ct:instance-list servers { ct:instance-type ServerInstance; }
      ct:instance-list images { ct:instance-type VirtualMachineImage; }
      ct:instance-list flavors { ct:instance-type VirtualMachineFlavor; }
    }

    container networking {
      if-feature has-networking;
      description "Contains networking related resources";
        
      ct:instance-list networks { ct:instance-type Network; }
      ct:instance-list subnets { ct:instance-type SubNetwork; }
      ct:instance-list ports { ct:instance-type SwitchPort; }
      //ct:instance-list routers { ct:instance-type Router; }
    }
  }
}
