module multi-vim {
  namespace "http://github.com/stormstack/stormforge";
  prefix mvim;

  import storm-common-models { prefix scm; }
  import complex-types { prefix ct; }

  description
    "Virtualized Infrastructure Manager Data Models with complex types and
     typed instance identifiers representing Resource providers,
     pools, capacities, reservations, etc.";
  
  revision 2015-03-16 {
    description
      "The 'multi-vim' YANG module is modeled using 'yang-storm' which
       natively provides complex types and typed instance identifiers.
       This module provides various collections of data models defined
       in 'storm-common-models' schema for instance based management";
  }

  feature multi-provider {
    description "If supported, the endpoint can be used manage one or more resource providers";
  }

  // MAIN CONTAINER

  container multi-vim {
    description "Top-level node of the multi-vim data model";
    ct:instance-list providers {
      if-feature multi-provider;
      description "Aggregate collection of all registered ResourceProvider instances";
      ct:instance-type scm:ResourceProvider;
    }
  }
  
  rpc list-providers;
  rpc add-provider;
  rpc remove-provider;
}
