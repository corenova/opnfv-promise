module opnfv-promise {
  namespace "urn:opnfv:vim:promise";
  prefix prom;

  import opnfv-promise-models { prefix opm; }
  import complex-types { prefix ct; }

  description
    "OPNFV Promise Resource Reservation/Allocation controller module";
  
  revision 2015-04-16 {
    description
      "Initial revision.";
  }

  // MAIN CONTAINER

  container promise {
    ct:instance-list reservations {
      description "Aggregate collection of all registered ResourceReservation instances";
      ct:instance-type opm:ResourceReservation;
    } 
  }
  
  rpc list-reservations;
  rpc create-reservation;
  rpc cancel-reservation;

  notification reservation-event;
  notification capacity-event;
  notification allocation-event;
}
